module ietf-netconf-otlp-baggage {
  namespace "urn:ietf:params:xml:ns:yang:tbdbaggage";
  prefix ietf-netconf-otlpbg;

  import ietf-netconf {
    prefix nc;
  }

  import ietf-netconf-nmda {
    prefix ncds;
  }

  import ietf-netconf-otlp-context {
    prefix ietf-netconf-otlpc;
  }


  organization
     "IETF NETCONF (Network Configuration) Working Group";

  contact
    "WG Web:   <http://tools.ietf.org/wg/netconf/>
    WG List:  <mailto:netconf@ietf.org>";
  
  description
    "When propagating telemetry information across entities,
    the baggage extension represents represents a set of 
    user-defined properties associated with a distributed request.

    This specification is based on the work by the W3C on its
    current working Draft '17 June 2022': https://www.w3.org/TR/baggage/

    Copyright (c) 2022 IETF Trust and the persons identified as
    authors of the code.  All rights reserved.

    Redistribution and use in source and binary forms, with or
    without modification, is permitted pursuant to, and subject to
    the license terms contained in, the Simplified BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.

    The key words 'MUST', 'MUST NOT', 'REQUIRED', 'SHALL', 'SHALL
    NOT', 'SHOULD', 'SHOULD NOT', 'RECOMMENDED', 'NOT RECOMMENDED',
    'MAY', and 'OPTIONAL' in this document are to be interpreted as
    described in BCP 14 (RFC 2119) (RFC 8174) when, and only when,
    they appear in all capitals, as shown here.
    ";
  
  revision 2022-08-29 {
    description
      "Initial revision";
    reference
      "RFC XXX";
  }

typedef token {
  description "token is defined in [RFC7230], Section 3.2.6: https://tools.ietf.org/html/rfc7230#section-3.2.6";
  type string {
    //need pattern
  }
}

typedef value-type {
  description "baggage-octet = %x21 / %x23-2B / %x2D-3A / %x3C-5B / %x5D-7E
    US-ASCII characters excluding CTLs, whitespace, DQUOTE, comma, semicolon, and backslash";
  type string {
    //Need to add pattern "";
  }
}
grouping baggage-grouping {
  description "Representing and propagating a set of user-defined properties associated with a distributed request.";
  container baggage {
    list baggage-string {
      key key;
        // Note: specification claims that: Uniqueness of keys between multiple list-members in a baggage-string is not guaranteed. The order of duplicate entries SHOULD be preserved when mutating the list. "
      leaf key {
        type token;
      }
      leaf value {
        type value-type;
        }
      }

      list properties {
        key key;
        leaf key {
          type token;
        }
        leaf value {
          type value-type;
        }
        max-elements 179;
      }
    }
  }

  augment "/nc:edit-config/nc:input/ietf-netconf-otlpc:traces" {
    description
         "Add trace info as possible input.";
    uses baggage-grouping;
  }

  augment "/nc:copy-config/nc:input/ietf-netconf-otlpc:traces" {
    description
         "Add trace info as possible input.";
    uses baggage-grouping;
  }

  augment "/nc:delete-config/nc:input/ietf-netconf-otlpc:traces" {
    description
         "Add trace info as possible input.";
    uses baggage-grouping;
  }

  augment "/nc:lock/nc:input/ietf-netconf-otlpc:traces" {
    description
         "Add trace info as possible input.";
    uses baggage-grouping;
  }

  augment "/nc:unlock/nc:input/ietf-netconf-otlpc:traces" {
    description
         "Add trace info as possible input.";
    uses baggage-grouping;
  }
  
  augment "/nc:get/nc:input/ietf-netconf-otlpc:traces" {
    description
         "Add trace info as possible input.";
    uses baggage-grouping;
  }

  augment "/nc:kill-session/nc:input/ietf-netconf-otlpc:traces" {
    description
         "Add trace info as possible input.";
    uses baggage-grouping;
  }

  augment "/nc:commit/nc:input/ietf-netconf-otlpc:traces" {
    description
         "Add trace info as possible input.";
    uses baggage-grouping;
  }

  augment "/nc:discard-changes/nc:input/ietf-netconf-otlpc:traces" {
    description
         "Add trace info as possible input.";
    uses baggage-grouping;
  }

  augment "/nc:validate/nc:input/ietf-netconf-otlpc:traces" {
    description
         "Add trace info as possible input.";
    uses baggage-grouping;
  }

  augment "/ncds:get-data/ncds:input/ietf-netconf-otlpc:traces" {
    description
         "Add trace info as possible input.";
    uses baggage-grouping; 
  }

  augment "/ncds:edit-data/ncds:input/ietf-netconf-otlpc:traces" {
    description
         "Add trace info as possible input.";
    uses baggage-grouping; 
  }
}
